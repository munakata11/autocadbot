(setq old\_osmode (getvar "osmode"))(setvar "osmode" 0)(command "RECTANG" "0,0" "5,5" "")(setvar "osmode" old\_osmode)

(setq old\_osmode (getvar "osmode"))(setvar "osmode" 0)(command "CIRCLE" "5,5" 2.5 "")(setvar "osmode" old\_osmode)
